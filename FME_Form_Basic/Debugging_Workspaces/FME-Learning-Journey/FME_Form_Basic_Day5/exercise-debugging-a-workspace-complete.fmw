FME workspace exercise-debugging-a-workspace-complete.fmw
Title: BestPractice-Ex3-Complete

Parameters:
- SourceDataset_CSV2 = https://s3.amazonaws.com/FMEData/FMEData/Data/Emergency/Crime.csv   # Source CSV (Comma Separated Value) File(s)
- SourceDataset_MITAB = https://s3.amazonaws.com/FMEData/FMEData/Data/Parks.zip   # Source MapInfo TAB File(s)
- SourceDataset_OSM = https://s3.amazonaws.com/FMEData/FMEData/Data/OpenStreetMap/leisure.osm   # Source OpenStreetMap File(s)

Readers:
- FILEGDB_1: FILEGDB from https://s3.amazonaws.com/FMEData/FMEData/Data/Addresses/Addresses.gdb.zip
- CSV2_1: CSV2 from $(SourceDataset_CSV2)
- MITAB_1: MITAB from $(SourceDataset_MITAB)
- OSM_1: OSM from $(SourceDataset_OSM)

FeatureJoiner
    ATTR_CONFLICT_RES = Prefer Left
    GEOMETRY_HANDLING = Prefer Left
    JOIN_KEYS = JoinKey Block AUTO
    JOIN_MODE = Inner
    JOINED -> AttributeValueMapper
    UNJOINED_LEFT -> AttributeCreator
NeighborFinder
    CANDIDATES_FIRST = No
    INSERT_VERTEX = No
    K = 1
    MEASURES_FROM_CANDIDATE = Yes
    MEASURE_TYPE = Continuous
    MODE = Bases and Candidates
    TREAT_POLYGON_AS = Lines
    MATCHED -> AttributeRenamer
Note: Rename _distance to ParkDistance
AttributeRenamer
    ATTR_TABLE = RENAME_SET_DEFAULT _distance > PoolDistance
    KEEP_RENAMED_ONLY = no
    MISSING_INPUT_ATTRS = PRESERVE
    -> PointOnAreaOverlayer [POINT]
Creator
    GEOMTYPE = Geometry Object
    NUM = 1
    CREATED -> FeatureReader [INITIATOR]
PointOnAreaOverlayer
    ATTR_ACCUM_MODE = Merge Incoming
    ATTR_CONFLICT_RES = Use Original
    DEAGGREGATE_INPUT = Yes
    OV_ATTR = _overlaps
    POLYS_FIRST = NO
    POINT -> AttributeValueMapper_2

Bookmark: Addresses File Geodatabase
PostalAddress (reader FILEGDB_1)
    attributes: OBJECTID objectid, GlobalID guid, OWNERNM1 text(150), OWNERNM2 text(150), PSTLADDRESS text(250), PSTLCITY text(100), PSTLPROV text(25), INTSTATE text(5), INTPSTLCD text(10), COUNTRY text(100), REPRESENT text(14), STATUS text(9), LASTUPDATE date, LASTEDITOR text(50), POSTALCODE text(6)
    -> AttributeSplitter

Bookmark: Prepare Addresses to Join
AttributeSplitter
    ATTR_NAME = PSTLADDRESS
    DELIMITER = " "
    DROP_EMPTY_PARTS = NO
    LIST_NAME = _list
    TRIM_TYPE = BOTH
    -> AttributeManager
AttributeManager
    ATTR_TABLE:
      REMOVE OBJECTID (int32)
      REMOVE GlobalID (buffer)
      REMOVE OWNERNM1 (varchar(150))
      REMOVE OWNERNM2 (varchar(150))
      RENAME_SET_VALUE PSTLCITY > City (varchar(100))
      RENAME_SET_VALUE PSTLPROV > Province (varchar(25))
      REMOVE INTSTATE (varchar(5))
      REMOVE INTPSTLCD (varchar(10))
      RENAME_SET_VALUE COUNTRY > Country (varchar(100))
      REMOVE REPRESENT (varchar(14))
      REMOVE STATUS (varchar(9))
      REMOVE LASTUPDATE (datetime)
      REMOVE LASTEDITOR (varchar(50))
      RENAME_SET_VALUE POSTALCODE > PostalCode (varchar(6))
      SET_TO Number (varchar(200)) = @Value(_list{0})
      SET_TO Street (varchar(200)) = @Value(_list{1}) @Value(_list{2}) @Value(_list{3})
    -> StringReplacer
StringReplacer
    CASE = NO
    FIND_TEXT = ..$
    NO_MATCH = _FME_NO_OP_
    REGEXP = YES
    REPLACE_TEXT = XX
    SRC_ATTRS = Number
    -> StringCaseChanger
StringCaseChanger
    ATTRCHOICE = SELECTED
    ATTRLIST = Street
    CHANGE_TYPE = upper
    -> AttributeManager_2
Note: Create JoinKey to merge with Crimes Block
AttributeManager_2
    ATTR_TABLE = SET_TO JoinKey (varchar(200)) = @Trim(@Value(Number) @Value(Street))
    -> FeatureJoiner [LEFT]

Bookmark: Crime CSV
Crime (reader CSV2_1)
    attributes: ID string, Type string, Month string, Block string
    -> FeatureJoiner [RIGHT]

Bookmark: Merge Crime data
AttributeValueMapper
    LUT = Commercial BE,10,Mischief Over $5000,8,Mischief Under $5000,2,Thef Of Auto Under $5000,4,Theft From Auto Over $5000,7,Theft From Auto Under $5000,3,Theft Of Auto Over $5000,6
    MAPPING_DIRECTION = FORWARD
    SRC = Type
    VAL_ATTR = CrimeValue
    -> Aggregator
Aggregator
    ACCUM_ATTRS_NAME = Drop Incoming Attributes
    AGGREGATE_TYPE = Homogeneous Collection (If Possible)
    GROUP_BY = PSTLADDRESS
    LIST_ATTRS_TO_INCLUDE = _list{} Block City Country CrimeValue ID JoinKey Month Number PostalCode Province PSTLADDRESS Street Type
    LIST_NAME = CrimeList
    MODE = Geometry - Assemble One Level
    SEP = ,
    SUM = CrimeValue
    AGGREGATE -> CenterPointReplacer
CenterPointReplacer
    POINTTYPE = CENTER
    POINT -> NeighborFinder [BASE]
AttributeCreator
    ATTR_TABLE = SET_TO CrimeValue (uint8) = 0
    -> NeighborFinder [BASE]

Bookmark: Swimming Pools OSM
leisure (reader OSM_1)
    attributes: created_by xml_buffer, area xml_buffer, layer xml_buffer, tag{}.k xml_buffer, tag{}.v xml_buffer, nd{}.ref xml_buffer, member{}.type xml_buffer, member{}.ref xml_buffer, member{}.role xml_buffer, osm_feature_type xml_buffer, osm_theme xml_buffer, sport xml_buffer, source xml_buffer, type xml_buffer, access xml_buffer, addr:street xml_buffer, website xml_buffer, boundary xml_buffer, building xml_buffer, name xml_buffer, leisure xml_buffer
    -> Tester
Tester
    BOOL_OP = OR
    TEST_CLAUSE = TEST @Value(leisure) = swimming_pool
    TEST_MODE = TEST
    PASSED -> Reprojector
Reprojector
    DEST = UTM83-10
    INTERPOLATION_TYPE_NAME = Nearest Neighbor
    RASTER_CELL_SIZE = Preserve Cells
    RASTER_TOLERANCE = 0.0
    REPROJECTED -> NeighborFinder [CANDIDATE]
Parks (reader MITAB_1) [off]
    attributes: ParkId smallint, RefParkId smallint, ParkName char(40), NeighborhoodName char(40), VisitorCount smallint, TreeCount smallint, DogPark char(1), Washrooms char(1), SpecialFeatures char(1)
    -> NeighborFinder [CANDIDATE]

Bookmark: Planning Geopackage
Note: Read in NoiseControlAreas
FeatureReader
    ATTRIBUTES = BusinessImprovementAreas,"AreaID,AreaName,LastUpdated,id",HistoricAreas,"ZoneID,ZoneName,ZoneCategory,ZoneLocation,ZoneDescription,ZonePoliciesPDF,LastUpdated,id",NoiseControlAreas,"AreaID,AreaName,AreaDescription,LastUpdated,id",ViewCones,"ViewID,ViewDescription,LastUpdated,id"
    ATTR_ACCUM_MODE = Only Use Result
    COMBINE_GEOM = Use Result
    DATASET = https://s3.amazonaws.com/FMEData/FMEData/Data/Planning/PlanningRestrictions.gpkg
    FEATURETYPES = NoiseControlAreas
    FORMAT = OGCGEOPACKAGE
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = YES
    OGCGEOPACKAGE_READ_BOOLEANS_AS_YES_NO = YES
    OGCGEOPACKAGE_READ_NULLS = YES
    OGCGEOPACKAGE_USE_SEARCH_ENVELOPE = NO
    ORDER_RESULTS = No
    OUTPUT_ADD_SCHEMA_ATTRIBUTES = NO
    OUTPUT_FEATURES_DISPLAY = Schema and Data Features
    NoiseControlAreas -> PointOnAreaOverlayer [AREA]

Bookmark: Clean up attributes
AttributeValueMapper_2
    DEFAULT_VALUE = 0
    LUT = Schedule C,200,Schedule F,50,Intermediate,100
    MAPPING_DIRECTION = FORWARD
    SRC = AreaName
    VAL_ATTR = NoiseZoneScore
    -> AttributeKeeper
Note: Only keep ParkDistance, CrimeValue and ZoneNoiseScore
AttributeKeeper
    CREATE_BULK_MODE_FEATURES = NO
    KEEP_ATTRS = CrimeValue,NoiseZoneScore,PoolDistance
    -> ExpressionEvaluator
Note: Calculate Walkability score
ExpressionEvaluator
    ACTION = Create New Attribute
    EXPRESSION = @Value(PoolDistance) + @Value(CrimeValue) - @Value(NoiseZoneScore)
    VAL_ATTR = Walkability
