FME workspace exercise-flood-risk-project-complete.fmw

Parameters:
- SourceDataset_CDED_3 = https://s3.amazonaws.com/FMEData/FMEData/Data/ElevationModel/DEM-Clipped.dem   # Source Canadian Digital Elevation Data (CDED) File(s)
- SourceDataset_FILEGDB = https://s3.amazonaws.com/FMEData/FMEData/Data/Addresses/Addresses.gdb.zip   # File Geodatabase
- SourceDataset_GML_3 = https://s3.amazonaws.com/FMEData/FMEData/Data/Boundaries/CoastalZones.zip   # Source Geography Markup Language (GML) File(s)

Readers:
- CDED_1: CDED from $(SourceDataset_CDED_3)
- FILEGDB_1: FILEGDB from $(SourceDataset_FILEGDB)
- GML_1: GML from $(SourceDataset_GML_3)

Note: PostalAddress: Addresses [FILEGDB]
PostalAddress (reader FILEGDB_1)
    attributes: OBJECTID objectid, GlobalID guid, OWNERNM1 text(150), OWNERNM2 text(150), PSTLADDRESS text(250), PSTLCITY text(100), PSTLPROV text(25), INTSTATE text(5), INTPSTLCD text(10), COUNTRY text(100), REPRESENT text(14), STATUS text(9), LASTUPDATE date, LASTEDITOR text(50), POSTALCODE text(6)
    -> PointOnAreaOverlayer [POINT]
Note: CoastalZones [GML]
_100m (reader GML_1)
    attributes: Zone xml_int16, gml_surfaceProperty xml_geometry, gml_multiSurfaceProperty xml_geometry
    -> PointOnAreaOverlayer [AREA]
_200m (reader GML_1)
    attributes: Zone xml_int16, gml_surfaceProperty xml_geometry, gml_multiSurfaceProperty xml_geometry
    -> PointOnAreaOverlayer [AREA]
_300m (reader GML_1)
    attributes: Zone xml_int16, gml_surfaceProperty xml_geometry, gml_multiSurfaceProperty xml_geometry
    -> PointOnAreaOverlayer [AREA]

Bookmark: Get Coastal Zone
PointOnAreaOverlayer
    ATTR_ACCUM_MODE = Merge Incoming
    ATTR_CONFLICT_RES = Use Original
    DEAGGREGATE_INPUT = Yes
    OV_ATTR = _overlaps
    POLYS_FIRST = NO
    POINT -> Tester
Tester
    BOOL_OP = OR
    TEST_CLAUSE = TEST @Value(_overlaps) = 1
    TEST_MODE = TEST
    PASSED -> PointOnRasterValueExtractor [POINT]

Bookmark: Get Elevation
Note: CDED: DEM-Clipped [CDED]
CDED (reader CDED_1)
    -> Reprojector
Reprojector
    DEST = UTM83-10
    INTERPOLATION_TYPE_NAME = Nearest Neighbor
    RASTER_CELL_SIZE = Preserve Cells
    RASTER_TOLERANCE = 0.0
    REPROJECTED -> PointOnRasterValueExtractor [RASTER]
PointOnRasterValueExtractor
    INTERPOLATION_TYPE_NAME = Nearest Neighbor
    POINT -> AttributeRenamer
AttributeRenamer
    ATTR_TABLE = RENAME_SET_DEFAULT _band{0}.value > Elevation
    KEEP_RENAMED_ONLY = no
    MISSING_INPUT_ATTRS = PRESERVE
    -> AttributeManager

Bookmark: Get Flood Risk Score
AttributeManager
    ATTR_TABLE = SET_TO FloodRisk (varchar(200)) = FME_CONDITIONAL:DEFAULT_VALUE'_FME_NO_OP_'BOOL_OP;AND;COMPOSITE_TEST;1 AND 2;TEST @Value(Zone) = 100;TEST @Value(Elevation) = 10'1'BOOL_OP;COMPOSITE;COMPOSITE_TEST;( 1 AND 2 ) OR ( 3 AND 4 );TEST @Value(Zone) = 200;TEST @Value(Elevation) <= 10;TEST @Value(Zone) = 100;TEST @Value(Elevation) <= 25'2'BOOL_OP;COMPOSITE;COMPOSITE_TEST;( 1 AND 2 ) OR ( 3 AND 4 ) OR ( 5 AND 6 );TEST @Value(Zone) = 300;TEST @Value(Elevation) <= 10;TEST @Value(Zone) = 200;TEST @Value(Elevation) <= 25;TEST @Value(Zone) = 100;TEST @Value(Elevation) <= 60'3'BOOL_OP;COMPOSITE;COMPOSITE_TEST;( 1 AND 2 ) OR ( 3 AND 4 );TEST @Value(Zone) = 300;TEST @Value(Elevation) <= 25;TEST @Value(Zone) = 200;TEST @Value(Elevation) <= 60'4'BOOL_OP;AND;COMPOSITE_TEST;1 AND 2;TEST @Value(Zone) = 300;TEST @Value(Elevation) <= 60'5'FME_NUM_CONDITIONS6___
    -> Inspector
Inspector
    TACKATTRS = FloodRisk
