FME workspace exercise-set-reader-and-writer-parameters-complete.fmw

Parameters:
- SourceDataset_FILEGDB = https://s3.amazonaws.com/FMEData/FMEData/Data/CommunityMapping/CommunityMap.gdb.zip   # File Geodatabase
- DestDataset_GML = C:\FMEData\Output\Training\Output.gml   # Destination Geography Markup Language (GML) File
- DestDataset_SQLITE3 = C:\FMEData\Output\Training\Parks.sqlite   # SQLite Database

Readers:
- FILEGDB_1: FILEGDB from $(SourceDataset_FILEGDB)

Writers:
- GML_1: GML to $(DestDataset_GML)
- SQLITE3_1: SQLITE3 to $(DestDataset_SQLITE3)

Tester
    BOOL_OP = OR
    TEST_CLAUSE = TEST @Value(ParkName) = Stanley Park
    TEST_MODE = TEST
    PASSED -> AttributeCreator
AttributeCreator
    ATTR_TABLE:
      SET_TO fme_db_operation (varchar(6)) = UPDATE
      SET_TO ParkName (varchar(30)) = Spapəy̓əq (Stanley Park)
    -> Parks (writer SQLITE3_1)

Bookmark: Reader Feature Types
CommunityCentres (reader FILEGDB_1)
    attributes: CentreName text(30), CentreAddress text(30), CentreURL text(50), OBJECTID objectid
    -> CommunityCentres (writer GML_1)
FoodVendors (reader FILEGDB_1)
    attributes: VendorID smallint, VendorName text(48), VendorDescription text(16), OBJECTID objectid
    -> FoodVendors (writer GML_1)
TransitStations (reader FILEGDB_1)
    attributes: StationName text(30), OBJECTID objectid
    -> TransitStations (writer GML_1)
Parks (reader FILEGDB_1)
    attributes: ParkName text(30), ParkAddress text(50), ParkURL text(100), OBJECTID objectid
    -> Parks (writer GML_1)
    -> Tester

Bookmark: Writer Feature Types
CommunityCentres (writer GML_1)
    attributes: CentreName xml_char(30), CentreAddress xml_char(30), CentreURL xml_char(50), OBJECTID xml_int32
FoodVendors (writer GML_1)
    attributes: VendorID xml_int16, VendorName xml_char(48), VendorDescription xml_char(16), OBJECTID xml_int32
TransitStations (writer GML_1)
    attributes: StationName xml_char(30), OBJECTID xml_int32
Parks (writer GML_1)
    attributes: ParkName xml_char(30), ParkAddress xml_char(50), ParkURL xml_char(100), OBJECTID xml_int32
Note: SQLite
Parks (writer SQLITE3_1)
    attributes: ParkName varchar(30), ParkAddress varchar(50), ParkURL varchar(100), OBJECTID integer
