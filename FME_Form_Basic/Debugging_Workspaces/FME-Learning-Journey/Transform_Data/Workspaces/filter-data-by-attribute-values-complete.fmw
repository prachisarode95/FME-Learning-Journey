FME workspace filter-data-by-attribute-values-complete.fmw

Parameters:
- DestDataset_FILEGDB = C:\FMEData\Output\Training\BusinessOwners.gdb   # File Geodatabase

Writers:
- FILEGDB_1: FILEGDB to $(DestDataset_FILEGDB)

AttributeManager
    ATTR_TABLE:
      REMOVE _creation_instance (uint64)
      REMOVE _response_body (buffer)
      REMOVE _http_status_code (buffer)
      REMOVE json_type (buffer)
      REMOVE json_index (uint32)
      RENAME_SET_VALUE Last Name > last_name (varchar(10))
      RENAME_SET_VALUE First > first_name (varchar(11))
      RENAME_SET_VALUE Company > company (varchar(40))
      REMOVE Latitude (real64)
      RENAME_SET_VALUE License Number > license_number (varchar(6))
      REMOVE Longitude (real64)
    -> DatabaseJoiner
DatabaseJoiner
    ATTR_ACCUM_MODE = Merge Joined
    ATTR_CONFLICT_RES = Use Original
    CACHE_SIZE = 5000
    DATASET = FME Training PostGIS Database
    FORMAT = POSTGRES
    JOIN_KEYS = license_number revoked_license
    MATCH_MULTIPLE_DISPLAY = Create a feature for each match
    MATCH_RULE_DISPLAY = Match All (1:M)
    POSTGRES_CREATE_FEATURE_TABLES_FROM_DATA = Yes
    POSTGRES_NAMED_CONNECTION = FME Training PostGIS Database
    POSTGRES_QUERY_FEATURE_TYPES_FOR_MERGE_FILTERS = Yes
    POSTGRES_READ_TIME_WITH_TIMEZONE = Yes
    POSTGRES_SCHEMAS_FOR_TABLE_LISTING = public
    PREFETCH_EXHAUSTIVE = Yes
    TABLE = public.revoked_licenses
    UNJOINED -> Tester
Tester
    BOOL_OP = OR
    TEST_CLAUSE = TEST @Value(company) NOT_= Arcu Ltd
    TEST_MODE = TEST
    PASSED -> BusinessOwners (writer FILEGDB_1)
CRCCalculator
    ALG_CHOICES = CRC-32
    CRC_ATTR = _crc
    CRC_TYPE = GEOM_ENCODED

Bookmark: Source Data
Creator
    GEOMTYPE = Geometry Object
    NUM = 1
    CREATED -> HTTPCaller
HTTPCaller
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://s3.amazonaws.com/FMEData/FMEData/Data/Planning/BusinessOwners.json
    TRANSFER_TIMEOUT_LENGTH = 90
    USE_COOKIES = No
    VERIFY_SSL_CERTIFICATES = Yes
    -> JSONFragmenter
JSONFragmenter
    EXPLODE_FORMAT = JSON
    EXTRACT_ATTR = Yes
    JSON_ATTR = _response_body
    JSON_QUERY = json[*]
    NEW_ATTRIBUTES = Company varchar(40) First varchar(11) Last Name varchar(10) Latitude real64 License Number varchar(6) Longitude real64
    READ_FROM_FILE = NO
    RECURSIVE = YES
    REJECT_EMPTY_LISTS = YES
    FRAGMENTS -> VertexCreator
VertexCreator
    MEASURE_TYPE = Continuous
    MODE_NAME = Replace with Point
    XVAL = @Value(Longitude)
    YVAL = @Value(Latitude)
    -> CoordinateSystemSetter
CoordinateSystemSetter
    COORDSYS = LL84
    -> AttributeManager

Bookmark: Writer Feature Types
BusinessOwners (writer FILEGDB_1)
    attributes: last_name text(10), first_name text(11), company text(40), license_number text(6), _matched_records double
