FME workspace exercise-join-tables-complete.fmw
Title: Exercise: Join Tables

Parameters:
- SourceDataset_FILEGDB = https://s3.amazonaws.com/FMEData/FMEData/Data/CommunityMapping/CommunityMap.gdb.zip   # File Geodatabase
- SourceDataset_MITAB = https://s3.amazonaws.com/FMEData/FMEData/Data/Parks.zip   # Source MapInfo TAB File(s)

Readers:
- FILEGDB_2: FILEGDB from $(SourceDataset_FILEGDB)
- MITAB_2: MITAB from $(SourceDataset_MITAB)

Note: Parks: Parks [MITAB]
Parks (reader MITAB_2)
    attributes: ParkId smallint, RefParkId smallint, ParkName char(40), NeighborhoodName char(40), VisitorCount smallint, TreeCount smallint, DogPark char(1), Washrooms char(1), SpecialFeatures char(1)
    -> FeatureJoiner [LEFT]
Note: Parks: Community Mapping [FILEGDB]
Parks (reader FILEGDB_2)
    attributes: ParkName text(30), ParkAddress text(50), ParkURL text(100), OBJECTID objectid
    -> FeatureJoiner [RIGHT]
FeatureJoiner
    ATTR_CONFLICT_RES = Prefer Left
    GEOMETRY_HANDLING = Prefer Left
    JOIN_KEYS = ParkName ParkName STRING
    JOIN_MODE = Left
    JOINED -> AttributeManager
    <REJECTED> -> AttributeManager
AttributeManager
